;..........................................................................
; Return T if p3 is right of vector p1 p2
(defun rightside ( p1 p2 p3 / p4 ang12 ndist normdist)
	(defun normdist ( p1 p2 p3 / p4 )
 	   (setq    p4 (polar p3 (- (angle p1 p2) (/ pi 2.0)) 1.0))
  	           (inters p1 p2 p3 p4 nil)
	)
    (setq ang12 (angle p1 p2)
             p4 (normdist p1 p2 p3)
          ndist (distance p3 p4)
             p4 (polar p4 (+ ang12 (/ pi 2.0)) ndist)
    )
    (grdraw p1 p2 1)
    (grdraw p2 p3 2)
    (grdraw p2 p4 3)
    (not (equal p3 p4 0.000000001))
)
 (defun c:test ()
  (princ "\nTest is : ")
  (setq p1 (getpoint "\np1: ")
        p2 (getpoint p1 "\np2: ")
        p3 (getpoint p2 "\np3: ")
  )
  (rightside p1 p2 p3)
)
;..........................................................................
